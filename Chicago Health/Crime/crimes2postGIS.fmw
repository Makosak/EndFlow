FME workspace crimes2postGIS.fmw

Parameters:
- SourceDataset_CSV2 = $(FME_MF_DIR)crimes.csv   # Source CSV (Comma Separated Value) File(s)
- DestDataset_POSTGRES = GeoDaRCC   # Connection
- SourceDataset_ESRISHAPE_3 = https://data.cityofchicago.org/api/geospatial/5jrd-6zik?method=export&format=Shapefile   # Source Esri Shapefile(s)

Readers:
- CSV2_1: CSV2 from $(SourceDataset_CSV2) in EPSG4326
- ESRISHAPE_1: ESRISHAPE from $(SourceDataset_ESRISHAPE_3) in EPSG4326

Writers:
- POSTGRES_1: POSTGRES to $(DestDataset_POSTGRES) in EPSG4326

VertexCreator
    XVAL = @Value(Longitude)
    MODE_NAME = Add Point
    YVAL = @Value(Latitude)
    -> Inspector
Inspector
indicator_crimes (writer POSTGRES_1)
    attributes: iucr text, domestic text, community_area int4, year int4, latitude numeric(20,10), longitude numeric(20,10), category text, fme_rejection_code text

Bookmark: CensusTracts2010
  Downloads the 2010 Census Tracts shapefile from the Chicago Data Portal
geo_export_3e74a4da-e3f7-4bb2-a6b2-52cb68967046 (reader ESRISHAPE_1)
    attributes: statefp10 char(254), countyfp10 char(254), tractce10 char(254), namelsad10 char(254), commarea char(254), geoid10 char(254), commarea_n number(33,31), name10 char(254), notes char(254)
    -> VertexCreator

Bookmark: crimes.csv
  Reads the locally processed crimes.csv file
CSV (reader CSV2_1)
    attributes: IUCR string, Domestic string, Community Area string, Year string, Latitude string, Longitude string, Category string
    -> VertexCreator
